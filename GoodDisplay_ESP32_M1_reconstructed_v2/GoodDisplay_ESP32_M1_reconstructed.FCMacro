# Good Display ESP32-M1 reconstructed mechanical model
# Units: mm. Origin = lower-left PCB corner, component side up.
# Board 48 x 66 x 1.0 mm is published. Peripheral XY positions reconstructed
# from the official orthographic product image and checked against the
# 18 x 25.5 mm ESP32-WROOM-32D footprint.
import FreeCAD as App, Part
from FreeCAD import Vector
try:
    doc=App.ActiveDocument
    if doc: App.closeDocument(doc.Name)
except: pass
doc=App.newDocument('GoodDisplay_ESP32_M1_Reconstructed')

def feat(name,shape,color):
    o=doc.addObject('PartDesign::Feature',name); o.Shape=shape; o.Label=name; o.ViewObject.ShapeColor=color; return o

def box(name,x,y,z,w,d,h,color=(0.55,0.55,0.55),r=0):
    # centered x/y box
    s=Part.makeBox(w,d,h,Vector(x-w/2,y-d/2,z))
    return feat(name,s,color)

def cyl(name,x,y,z,d,h,color=(0.5,0.5,0.5)):
    return feat(name,Part.makeCylinder(d/2,h,Vector(x,y,z)),color)

# PCB outline with rounded corners generated by fused boxes/cylinders
W,H,T,R=48.0,66.0,1.0,2.35
s=Part.makeBox(W-2*R,H,T,Vector(R,0,0)).fuse(Part.makeBox(W,H-2*R,T,Vector(0,R,0)))
for x in (R,W-R):
    for y in (R,H-R): s=s.fuse(Part.makeCylinder(R,T,Vector(x,y,0)))
for x,y in [(2.40,2.45),(45.60,2.45),(2.40,63.65),(45.60,63.65)]:
    s=s.cut(Part.makeCylinder(1.075,T+0.4,Vector(x,y,-0.2)))
pcb=feat('PCB_48x66x1',s,(0.03,0.20,0.45))

box('U5_ESP32_WROOM_32D',32.55,53.70,1.0,18.0,25.5,3.10,(0.58,0.58,0.58)); box('ESP32_Antenna',32.55,63.2,4.11,17.5,5.0,0.20,(0.05,0.05,0.05))
box('P2_USB_C',1.85,52.45,1.0,8.5,8.9,3.15,(0.72,0.72,0.72)); box('P2_USB_C_Port',-2.15,52.45,1.65,1.2,5.7,1.55,(0.1,0.1,0.1))
for n,x in [('RST',9.90),('BOOT',13.75)]:
    box(n+'_BODY',x,63.55,1.0,4.0,4.2,1.5,(0.55,0.55,0.55)); cyl(n+'_ACTUATOR',x,63.55,2.5,1.75,0.8,(0.2,0.2,0.2))
box('P4_RESE_SWITCH',46.1,49.85,1.0,3.9,8.2,2.05,(0.55,0.55,0.55)); box('P4_RESE_SLIDER',48.05,49.85,1.55,2.2,1.3,0.85,(0.92,0.90,0.72))
box('P1_BAT_SH1_0',11.15,33.75,1.0,5.0,5.0,3.0,(0.91,0.91,0.83))
box('POWER_SWITCH',2.55,33.25,1.0,5.5,8.3,2.25,(0.5,0.5,0.5)); box('POWER_ACTUATOR',-1.25,33.25,1.65,4.8,1.35,0.95,(0.12,0.12,0.12))
box('U4_MICRO_SD_SOCKET',7.25,20.45,1.0,14.6,15.4,1.75,(0.64,0.64,0.62)); box('MICRO_SD_ENTRY',-0.2,20.45,1.35,1.2,10.2,0.8,(0.18,0.18,0.18))
box('S1_KEY',1.10,8.75,1.0,4.2,4.7,2.2,(0.2,0.2,0.2)); box('S1_KEY_ACTUATOR',-1.25,8.75,1.65,3.1,1.4,0.9,(0.85,0.84,0.70))
box('RT_FRONTLIGHT_TRIMMER',6.05,2.85,1.0,3.8,3.8,1.8,(0.72,0.72,0.68)); cyl('RT_ADJUST_SCREW',6.05,2.85,2.8,2.0,0.45,(0.45,0.45,0.45))
box('P8_VOLTAGE_SELECT',13.0,2.35,1.0,9.1,3.6,1.8,(0.62,0.62,0.62)); box('P8_ACTUATOR',13.0,-0.15,1.45,1.45,2.2,0.8,(0.15,0.15,0.15))
box('SS1_FRONTLIGHT_HV_DIP',21.35,2.95,1.0,4.6,5.1,2.15,(0.1,0.1,0.08))
for i in range(4): box('SS1_LEVER_%d'%(i+1),20.0+i*0.9,2.95,3.15,0.45,1.2,0.45,(0.9,0.66,0.05))
box('P6_FRONTLIGHT_FPC',32.15,2.55,1.0,6.7,5.1,2.1,(0.92,0.92,0.88)); box('P6_ENTRY',32.15,-0.35,1.45,4.9,1.7,0.7,(0.1,0.1,0.1))
for n,y in [('TP2_TOUCH_FPC',34.80),('TP1_TOUCH_FPC',27.05)]:
    box(n,45.25,y,1.0,5.4,7.35,2.0,(0.92,0.92,0.88)); box(n+'_ENTRY',48.15,y,1.45,1.6,5.25,0.75,(0.1,0.1,0.1))
box('P5_EPAPER_24PIN_FPC',45.55,14.85,1.0,4.9,16.0,2.15,(0.93,0.92,0.83)); box('P5_ENTRY',48.15,14.85,1.45,1.7,13.3,0.75,(0.1,0.1,0.1))
# visual landmarks
box('U3_USB_UART_SOIC',17.05,51.7,1.0,4.3,9.0,1.25,(0.12,0.12,0.12)); box('U8_MAIN_IC',21.2,31.6,1.0,5.4,5.4,1.05,(0.1,0.1,0.1)); box('L1_470',25.9,20.1,1.0,4.5,4.5,2.2,(0.18,0.18,0.18)); box('L2',23.0,9.0,1.0,4.2,4.2,2.0,(0.16,0.16,0.16))
# Useful enclosure clearance objects, hidden by default
keep=doc.addObject('App::DocumentObjectGroup','CASE_KEEPOUTS')
for n,x,y,w,d,h in [
 ('CLR_USB_C',-2.3,52.45,8.0,7.4,5.0),('CLR_MICROSD',-3.0,20.45,10.0,12.0,3.0),('CLR_POWER',-2.5,33.25,8.0,5.0,4.0),('CLR_KEY',-2.5,8.75,8.0,5.0,4.0),
 ('CLR_RESE',49.0,49.85,6.0,5.0,4.0),('CLR_TP2',49.5,34.8,8.0,7.0,4.0),('CLR_TP1',49.5,27.05,8.0,7.0,4.0),('CLR_P5',49.5,14.85,8.0,15.0,4.0),('CLR_P6',32.15,-3.0,7.0,8.0,4.0),('CLR_P8',13.0,-3.0,5.0,8.0,4.0)]:
    o=box(n,x,y,1.0,w,d,h,(0.9,0.2,0.2)); o.ViewObject.Transparency=75; o.ViewObject.Visibility=False; keep.addObject(o)

doc.recompute()
Gui.activeDocument().activeView().viewAxonometric(); Gui.activeDocument().activeView().fitAll()
